RFC-1212 DEFINITIONS ::= BEGIN
	-- RFC 1212 doesn't have any actual definitions and is only a definition
	-- document.  This file will satisfy the requirement of many MIBS for
	-- information from RFC1212.
END
